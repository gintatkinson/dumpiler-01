doc /* Structural Architecture for Subsystem 7 Formal Safety Traceability Verification */
package FormalSafetyTraceability {
    import DEAP_Compiler_System::*;

    doc /* Primary execution engine for Formal Safety, Traceability & Regulatory Verification */
    part def SafetyAssuranceEngine {
        port in metrology_in : MetrologyFlowPort;
        port in state_in : StateSolverPort;
        port out safety_out : SafetyPort;

        part graphBuilder : BipartiteGraphBuilder;
        part tierValidator : DisjointTierValidator;
        part sweepEngine : BidirectionalSweepEngine;
        part diagSink : DiagnosticSentinelSink;
    }

    doc /* Deterministic 7-tier bipartite DAG construction and reachability indexing */
    part def BipartiteGraphBuilder {
        port in ast_stream : ASTStreamPort;
        port out safety_out : SafetyPort;
    }

    doc /* Enforces strict disjoint tier partitioning and adjacent-only edges */
    part def DisjointTierValidator {
        port in ast_stream : ASTStreamPort;
        port out safety_out : SafetyPort;
    }

    doc /* Bidirectional forward and backward reachability sweeps */
    part def BidirectionalSweepEngine {
        port in ast_stream : ASTStreamPort;
        port out safety_out : SafetyPort;
    }

    doc /* Error sink and diagnostic sentinel emission for safety invariants */
    part def DiagnosticSentinelSink {
        port in diag_in : DiagnosticPort;
        port out safety_out : SafetyPort;
    }
}
